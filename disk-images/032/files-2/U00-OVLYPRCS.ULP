Procedure Edit_List; {Cant be Overlay as called by Select}
label
  dropout;
var
  C  : integer;
  ss,entry : str8;
  tempitem : labelprint;
  zf : FILE of labelcont;
  testq : real;

procedure update_it;
begin
  seek(batchfile,movetonum);
  write(batchfile,tempitem);
  clrframe(10,25);
  Display_queue;
end;

procedure disp_entry;
begin
  seek(batchfile,entrynum);
  read(batchfile,batchitem);
  gotoxy(1,entrynum+10);
  lowvideo;write('>',entrynum+1:2);normvideo;
  write('   Label= ',batchitem.labelname:10,' ');
  gotoxy(27,entrynum+10);
  write('Qty to Print= ');
  gotoxy(41,entrynum+10);
  write(batchitem.QtyToPrint,' ');
end; {or disp_entry}

begin
 clrframe(10,25);
 gotoxy(1,6);clreol;
 Repack_batchfile;
 display_queue;
 if maxnum>0 then
 REPEAT
  Key_use(Edit);
  gotoxy(1,8);write('Select Function above or press ESC to exit: ');clreol;
  read(kbd,ans);
  case ans of
   ^A : begin      {Delete Entry}
         repeat
           entry:='';
           gotoxy(1,8);
           write('Enter number of entry to Delete or press <ESC> to exit: ');
           clreol;
           repeat
             getinput(2,57,8,entry,'n',fin,1);
             val(entry,entrynum,j)
           until j=0;
          until (entrynum in [1..maxnum]) or (fin =TRUE);
          if fin=TRUE then goto dropout;
          entrynum:=entrynum-1;
          batchitem.QtyToPrint:=0;
          seek(batchfile,entrynum);
          write(batchfile,batchitem);
          clrframe(10,25);
          repack_batchfile;
          display_queue;
        end;
   ^F : begin      {Amend Qty}
         repeat
            entry:='';
            gotoxy(1,8);
            write('Enter number of entry to amend or press <ESC> to exit: ');
            clreol;
            repeat
             getinput(2,56,8,entry,'n',fin,1);
             val(entry,entrynum,j)
            until j=0;
         until (entrynum in [1..maxnum]) or (fin =TRUE);
         if fin=TRUE then goto dropout;
         entrynum:=entrynum-1;
         disp_entry;
         Str(batchitem.QtyToPrint,entry);
         inst:=false;
         repeat
          repeat
           getinput(5,41,entrynum+10,entry,'n',fin,1);
           val(entry,testq,j);
          until testq<=32000;
          val(entry,batchitem.QtyToPrint,j);
         until j=0;
         seek(batchfile,entrynum);
         write(batchfile,batchitem);
         gotoxy(1,entrynum+10);normvideo;
         write(entrynum+1:3);
         write('   Label= ',batchitem.labelname:10,' ');
         gotoxy(27,entrynum+10);
         write('Qty to Print= ',batchitem.QtyToPrint,'     ');
        end;
   ^S : begin     {Move Entry}
         repeat
          entry:='';
          gotoxy(1,8);
          write('Enter number of entry to Move or press <ESC> to exit: ');
          clreol;
          repeat
           getinput(2,55,8,entry,'n',fin,1);
           val(entry,entrynum,j)
          until j=0;
         until (entrynum in [1..maxnum]) or (fin =TRUE);
         if fin=TRUE then goto dropout;
         entrynum:=entrynum-1;
         disp_entry;
         repeat
          entry:='';
          gotoxy(1,8);write('Enter Position to move to: ');clreol;
          repeat
            getinput(2,28,8,entry,'n',fin,1);
            val(entry,movetonum,j)
          until j=0;
         until movetonum in [1..maxnum];
         movetonum:=movetonum-1;
         Tempitem:=batchitem;
         IF movetonum<entrynum then
         begin
           for C:=entrynum-1 downto movetonum do
           begin
             seek(batchfile,C);
             read(batchfile,batchitem);
             write(batchfile,batchitem);
           end;
           update_it;
         end
         ELSE
         begin
           if movetonum>entrynum then
           begin
             for C:=entrynum+1 to movetonum do
             begin
               seek(batchfile,C);
               read(batchfile,batchitem);
               seek(batchfile,filepos(batchfile)-2);
               write(batchfile,batchitem);
             end;
             update_it;
           end;
         end;
        end; {of move}
   ^P : if maxnum<15 then
        begin                                    {Insert entry}
          repeat
           entry:='';
           gotoxy(1,8);
           write('Enter position for new entry or press <ESC> to exit: ');
           clreol;
           repeat
            getinput(2,54,8,entry,'n',fin,1);
            val(entry,entrynum,j)
           until j=0;
          until (entrynum in [1..maxnum+1]) or (fin =TRUE);
          if fin=TRUE then goto dropout;
          entrynum:=entrynum-1;
          clrframe(10,25);
          labname:='';
          gotoxy(1,10);
          display_files('L'+labext,entrynum+12,labeldrive[1]);
          gotoxy(1,8); write('Enter Label Name: ');clreol;
          getinput(8,19,8,labname,'c',fin,1);
          assign(zf,labeldrive+labname+'.L'+labext);
          {$I-} reset(zf);  {$I+}
          i:=ioresult;
          if i <>0 then
          begin
            gotoxy(1,8);lowvideo;
            write('Label ',labname,' is not on drive ',labeldrive);
            write('Error ',i);
            normvideo; delay(4000);
            close(zf);
          end
          else
          begin
           if entrynum=maxnum+1 then
            maxnum:=maxnum+1
           else
            for C:=maxnum-1 downto entrynum do
            begin
              seek(batchfile,C);
              read(batchfile,batchitem);
              write(batchfile,batchitem);
            end;
            str(nextnum,ss);
            qname:=labeldrive+'QUELAB'+ss;
            assign(tempf,qname+'.Q'+labext);
            rewrite(tempf);
            sccol(green);
            while not eof(zf) do
            begin
              read(zf,lab);
              write(tempf,lab);
              put_on_screen;
            end;
            if VarsExist=TRUE then
             Var_update;
            Num_of_copies;
            close(tempf); close(zf);
            nextnum:=nextnum+1;
            reset(numberfile);
            write(numberfile,nextnum);
            close(numberfile);
            repack_batchfile;
          end;
          clrframe(10,25);
          display_queue;
        end;   {of insert}
   #27  : goto dropout;
   ELSE  begin
          clrframe(10,25);
          display_queue;
         end;
  end; {of case}
dropout:
 UNTIL (fin=TRUE) or (ans=#27);
close(batchfile);reset(batchfile);
close(numberfile); reset(numberfile);
ans:=' ';
end;  {of edit_list}

{Overlay }Procedure exit_without_print;
Var
  ln : str14;
  z : byte;
begin
 close(batchfile); close(numberfile);
 clrframe(10,25);
 gotoxy(1,22);
end;  {of exit_without_print}

{Overlay }Procedure delete_list;
Var
  ln  : str14;
begin
 if Batchexists=TRUE then
 begin
  {$I-} reset(batchfile);{$I+}
  error:=ioresult;
  if error>0 then
  begin
    ermsg(error);
    exit;
  end;
  repack_batchfile; reset(batchfile);
  while not eof(batchfile) do
  begin
    read(batchfile,batchitem);
    ln:=labeldrive+batchitem.labelname+'.Q'+labext;
    assign(nf,ln);
    {$I-} reset(nf); {$I+}
    if ioresult=0 then
     erase(nf);
  end;
{$I-}
  close(batchfile);
  i:=ioresult;
  erase(batchfile);
  i:=ioresult;
{$I+}
 end;
 Batchexists:=FALSE;
end;  {of delete_list}

{Overlay }Procedure list_on_printer;
var
  line : integer;
begin
 if BatchExists=TRUE then
 begin
  case printertype of
    'P' : writeln(lst,chr(3),'INCHES;11');
    'E' : begin
           writeln(lst,chr(27),'C',chr(0),chr(11));
           writeln(lst,chr(27),'2');
          end;
  end; {of case}

  reset(batchfile);
  line:=1;
  writeln(lst,'Contents of Current Label Batch Print File.':60);
  writeln(lst,ConstStr('-',79));
  while not eof(batchfile) do
  begin
   read(batchfile,batchitem);
   with batchitem do
    writeln(lst,'Label ',line,'= ',labelname,'  Quantity = ',qtytoprint:5);
   line:=line+1;
  end;
  writeln(lst,chr(12));
 end;
end;  {of list_on_printer}

{Overlay }Procedure print_labels;
label
  dropout;
var
  numdone, entrynum, sl : integer;
  hold : char;
  ln : str14;
  sixline : sixbyte;
  bottom1,bottom2,right1,right2 : integer;
begin
  if BatchExists=TRUE then
  begin
   repeat
     clrframe(10,25);
     gotoxy(10,12);write('1.    Printronix - Straight.');
     gotoxy(10,13);write('2.    Epson - Straight.');
     gotoxy(10,15);write('3.    Printronix - Sideways.');
     gotoxy(10,16);write('4.    Epson - Sideways.');
     repeat
       gotoxy(1,8); clreol;
       write('Select Printing method, or ESC to exit.');
       read(kbd,ans);
      case ans of
       '1'     : printertype:='P';
       '2'     : printertype:='E';
       '4'     : begin
                  assign(f,progdrive+'SLP.COM');
                  {$I-} execute(f); {$I+}
                  if ioresult<>0 then
                  begin
                     gotoxy(1,8);lowvideo;
                     write('Epson sideways printing not available.');
                     normvideo; clreol; ans:=' ';
                     delay(2000);
                  end;
                 end;
       '3'     : begin
                  assign(f,progdrive+'PLP.COM');
                  {$I-} execute(f); {$I+}
                  if ioresult<>0 then
                  begin
                     gotoxy(1,8); lowvideo;
                     write('Printronix sideways printing not available.');
                     normvideo; clreol; ans:=' ';
                     delay(2000);
                  end;
                 end;

      end; {of case}
     until ans in ['1'..'6',#27];
     if ans=#27 then goto dropout;
     gotoxy(1,8);lowvideo;
     write('Press RETURN when printer is ON LINE, or ESC to exit.');
     normvideo;clreol;
     read(kbd,ans);
     if ans=#27 then goto dropout;
   until ans = ^M;
   case printertype of
    'P' : writeln(lst,chr(3),'INCHES;',labeldrop:3:1);
    'E' : writeln(lst,chr(27),'C',chr(0),chr(trunc(labeldrop)));
   end; {of case}
   write(lst,chr(12));
   clrframe(10,25);
   display_queue;
   reset(batchfile);entrynum:=1;
   while not eof(batchfile) do
   begin
     setup; numdone:=0;
     read(batchfile,batchitem);
     if batchitem.QtyToPrint>0 then
     begin
      ln:=batchitem.labelname;
      assign(lf,batchitem.QueName+'.Q'+labext);
      gotoxy(1,8);
      write('Label ',ln:8,' being read to colour screen....');
      clreol;
      gotoxy(1,entrynum+9);
      lowvideo; write('>',entrynum:2);normvideo;
      write('   Label= ',ln:10);
      gotoxy(27,entrynum+9);
      write('Qty to Print= ',batchitem.QtyToPrint);
      gotoxy(52,entrynum+9);
      write('Qty Printed= ',numdone,' ');
      {$I-} reset(lf);{$I+}
      error:=ioresult;
      if error<>0 then
      begin
        ermsg(error);
        goto dropout;
      end;
      sccol(green);
      while not eof(lf) do
      begin
        read(lf,lab);
        put_on_screen;
      end;
      close(lf);
      clreol;
      setcdp(1);
      top:=0; bottom1:=0; bottom2:=0;
      left:=0; right1:=0; right2:=0;
      twoscreens:=FALSE;
      reset(paramf);
      while not eof(paramf) do
      begin
        read(paramf,param);
        with param do
        begin
         case partition of
          1 : begin
                if by>bottom1 then bottom1:=by;
                if bx>right1 then right1:=bx;
              end;
          2 : begin
                if by>bottom2 then bottom2:=by;
                if bx>right2 then right2:=bx;
                twoscreens:=TRUE;
              end;
         end; {of case}
        end; {of with}
      end; {of while};
      assign(fname,workdrive+'DUMP6.DAT');
      rewrite(fname);
      dump_pluto(right1,bottom1,right2,bottom2);
      close(fname);
      gotoxy(1,8); write('Label ',ln:8,' being ');
      write('printed. Press ^K to stop after label being printed.');
      clreol;
      for numdone:=1 to batchitem.qtytoprint do
       begin
        reset(fname);
        repeat
          Blockread(fname,sixline,1);
          for count:=1 to 128 do
           output(sixline[count]);
        until eof(fname);
        write(lst,chr(12));
        gotoxy(41,entrynum+9);
        write(batchitem.QtyToPrint-numdone,' ');
        gotoxy(65,entrynum+9);
        write(numdone,' ');
        if keypressed then
         read(kbd,hold);
        if hold=^K then
        begin
          close(fname);
          with batchitem do
          begin
           QtyToPrint:=QtyToPrint-numdone;
           gotoxy(1,entrynum+9);normvideo;
           write(entrynum:3,'   Label= ',ln:10);
           gotoxy(27,entrynum+9);
           write('Qty to Print= ',QtyToPrint,' ');
           gotoxy(52,entrynum+9);
           write('Qty Printed= ',numdone,' ');
           clreol;
          end;
          seek(batchfile,filepos(batchfile)-1);
          write(batchfile,batchitem);
          close(batchfile);
          goto dropout;
        end;
       end;
       close(fname);
       with batchitem do
       begin
        QtyToPrint:=QtyToPrint-numdone;
        if QtyToPrint=0 then
          erase(lf);
        gotoxy(1,entrynum+9);normvideo;
        write(entrynum:3,'   Label= ',ln:10);
        gotoxy(27,entrynum+9);
        write('Qty to Print= ',QtyToPrint,' ');
        gotoxy(52,entrynum+9);
        write('Qty Printed= ',numdone,' ');
        clreol;
       end;
       seek(batchfile,filepos(batchfile)-1);
       write(batchfile,batchitem);
     end; {if qtytoprint>0}
     entrynum:=entrynum+1;
   end; {of while not eof batchfile}
   BatchExists:=FALSE;
   close(batchfile);
   erase(batchfile);
   dropout:
   ans:=' ';
  end;  {of if batchfile exists}

  clrframe(10,25);
  gotoxy(1,20);
end;  {of print_labels}

{Overlay }Procedure select_labels;
var
  labnams : array[1..15] of str8;
  NumOfLabs : integer;
  ss : str8;
begin
  if BatchExists=TRUE then
    exit;
  numOfLabs:=0;
  clrframe(10,25);
  gotoxy(1,10);write('Labels selected: ');clreol;
  gotoxy(1,13);
  write(ConstStr('*',79));
  labname:='';
  display_files('L'+labext,14,labeldrive[1]);
  REPEAT
    setup;
    Key_use(Select);
    VarsExist:=FALSE;
    gotoxy(1,8);write('Enter Label Name: ');
    clreol; gotoxy(19,8); read(kbd,command);
    case command of
     ^F : begin
           edit_list;
           reset(batchfile);
           while not eof(batchfile) do
           begin
             {$I-} read(batchfile,batchitem);{$I+}
             error:=ioresult;
             if error>0 then
             begin
              ermsg(error);
              exit;
             end;
             labnams[filepos(batchfile)]:=batchitem.labelname;
           end;
           NumOfLabs:=filesize(batchfile);
           clrframe(10,25);
           Key_use(Select);
           gotoxy(1,10);write('Labels selected: ');clreol;
           gotoxy(1,13);
           write(ConstStr('*',79));
           labname:='';
           gotoxy(1,11);
           for i:=1 to NumOfLabs do
            write(labnams[i]:10);
          end;
     ^P : begin
           close(batchfile);
          end;
     ^T : begin
            display_files('L'+labext,14,labeldrive[1]);
          end;
     ELSE begin
           if command >= ' ' then     {if a character}
           begin
             labname:=UpCaseStr(command);
             getinput(8,19,8,labname,'c',fin,2);
             assign(lf,labeldrive+labname+'.L'+labext);
             {$I-} reset(lf);  {$I+}
             j:=ioresult;
             if j <>0 then
             begin
               gotoxy(1,8);lowvideo;write('ERROR ',j,'  ');
               write(labname,'.L',labext,' is not on drive ');
               normvideo; delay(4000);
             end
             else
             begin
               NumOfLabs:=NumOfLabs+1;
               labnams[numOfLabs]:=labname;
               gotoxy(1,11);
               for i:=1 to NumOfLabs do
                write(labnams[i]:10);
               str(nextnum,ss);
               qname:=labeldrive+'QUELAB'+ss;
               assign(tempf,qname+'.Q'+labext);
               rewrite(tempf);
               sccol(green);
               while not eof(lf) do
               begin
                 read(lf,lab);
                 write(tempf,lab);
                 put_on_screen;
               end;
               if VarsExist=TRUE then
                Var_update;     {in edit.ulp}
               entrynum:=filesize(batchfile);
               Num_of_copies;
               close(tempf);
               nextnum:=nextnum+1;
               reset(numberfile);
               write(numberfile,nextnum);
               close(numberfile);
             end; {of else label exists}
           end; {if a character}
          end; {of else in case}
    end; {of case}
  UNTIL (command=^P) or (NumOfLabs=15);
end;  {of select_labels}
